(defun MainLayer ()
  (command "LINETYPE" "S" "BYLAYER" "" "LWEIGHT" 0.7 "" "COLOR" "white")
)

(defun AxisLayer ()
  (command "LINETYPE" "S" "CENTER" "" "LWEIGHT" 0.3 "" "COLOR" 30)
)

(defun SizeLayer ()
  (command "LINETYPE" "S" "BYLAYER" "" "LWEIGHT" 0.3 "" "COLOR" 150)
)

(defun c:gasket ()
  (command "OSNAP" "OFF")
  (command "SNAP" "OFF")
  (command "LTSCALE" 0.15)
  (command "LWDISPLAY" 1)
  (MainLayer)
  (command "CIRCLE" (list 0 0) "D" 92)
  (command "CIRCLE" (list 200 0) "D" 140)

  (command "ZOOM" "W" (list 75 235) (list 145 165))
  (command "CIRCLE" (list 110 200) "D" 50)
  (command "LINE" (list 97 200) (list 87 200) "")
  (command "OSNAP" "NEA")
  (command "ROTATE" (list 95 200) "" (list 110 200) -60)
  (command "MIRROR" (list 101 215) "" (list 110 200) (list 95 200) N)
  (AxisLayer)
  (command "XLINE" (list 110 200) (list 110 150) (list 150 200) "")
  (command "CIRCLE" (list 110 200) 30)
  (command "TRIM" (list 131.2 178.8) "" (list 145 200) (list 75 200) (list 110 235) (list 110 165) "")
  (command "ERASE" (list 131.2 178.8) "")
  (MainLayer)
  (command "CIRCLE" (list 110 200) 18)
  (command "OSNAP" "INT+END")
  (command "CIRCLE" (list 101.0 215.6) 5)
  (command "CIRCLE" (list 92.0 200.0) "")
  (command "CIRCLE" (list 101.0 184.4) "")
  (MainLayer)
  (command "CIRCLE" (list 101.0 215.6) "D" 6.5)
  (command "CIRCLE" (list 92.0 200.0) "")
  (command "CIRCLE" (list 101.0 184.4) "")
  (command "CIRCLE" (list 110 200) "D" 14)
  (command "TRIM" (list 88.5 203.5) (list 96.0 215.6) (list 96.0 184.4) "")
  (command (list 94.4 209.0) (list 94.4 191.0) (list 122.7 212.7) "")
  (command "ERASE" (list 88.5 203.5) (list 96.0 215.6) (list 96.0 184.4) "")
  (command "ARC" "C" (list 110 200) "@18<-60" "A" 120)
  (command "OSNAP" "END+PER")
  (command "LINE" (list 119.0 215.6) (list 122.5 221.7) "")
  (command "OSNAP" "NEA+CEN+END")
  (command "MIRROR" (list 120.8 218.6) "" (list 110 200) (list 140 200) "")
  (command "OSNAP" "NEA+MID")
  (command "TRIM" (list 120.8 218.6) (list 120.8 181.4) "" (list 131.7 212.5) "")
)
