(defun MainStyle ()
  (command "LINETYPE" "S" "BYLAYER" "" "LWEIGHT" 0.5 "" "COLOR" "white")
)
(defun AxisStyle ()
  (command "LINETYPE" "S" "CENTER" "" "LWEIGHT" 0.2 "" "COLOR" 40)
)
(defun SizeStyle ()
  (command "LINETYPE" "S" "BYLAYER" "" "LWEIGHT" 0.2 "" "COLOR" 140)
)
(defun c:two ()
  (setq top_left_vertical_axis_point (list 0 75))
  (setq bottom_left_vertical_axis_point (list 0 -75))
  (setq top_right_vertical_axis_point (list 200 45))
  (setq bottom_right_vertical_axis_point (list 200 -45))
  (setq left_horizontal_axis_point (list -75 0))
  (setq right_horizontal_axis_point (list 245 0))
  (setq select_left_inner_circle (list 34 30))
  (setq select_left_outer_circle (list -48 49))
  (setq left_inner_circle_dimension_point (list -70 -50))
  (setq left_outer_circle_dimension_point (list -40 80))
  (setq select_right_inner_circle (list 182 9))
  (setq select_right_outer_circle (list 239 -10))
  (setq right_inner_circle_dimension_point (list 250 -40))
  (setq right_outer_circle_dimension_point (list 240 40))
  (setq select_left_eighty_dimension_point (list 120 -60))
  (setq eighty_horizontal_dimension_point (list 200 -70))
  (setq two_hundred_horizontal_dimension_point (list 200 -90))
  (setq select_top_vertical_dimension (list 120 60))
  (setq select_bottom_vertical_dimension (list 120 -60))
  (setq vertical_dimension_point (list 270 60))
  (command "grid" "OFF")
  (command "OSNAP" "OFF")
  (command "SNAP" "OFF")
  (command "LWDISPLAY" 1)
  (AxisStyle)
  (command "LINE" top_left_vertical_axis_point bottom_left_vertical_axis_point "")
  (command "LINE" top_right_vertical_axis_point bottom_right_vertical_axis_point "")
  (command "LINE" left_horizontal_axis_point right_horizontal_axis_point "")
  (MainStyle)
  (command "ZOOM" "E")
  (command "CIRCLE" (list 0 0) "D" 92)
  (command "CIRCLE" (list 0 0) "D" 140)
  (command "CIRCLE" (list 200 0) "D" 40)
  (command "CIRCLE" (list 200 0) "D" 80)
  (command "PLINE" (list 200 40) (list 120 40) (list 120 60) (list 0 60) "")
  (command "MIRROR" (list 110 60) "" (list 200 0) (list 400 0) "N")
  (command "trim" select_left_outer_circle "" (list 20 60) (list 20 -60) "")
  (command "trim" (list 70 60) (list 70 -60) "" "NEA" (list 63 29) (list 161 10) "")
  (SizeStyle)
  (command "dimtxt" 7)
  (command "dimtoh" "ON")
  (command "dimasz" 7)
  (command "dimdiameter" "NEA" select_left_inner_circle left_inner_circle_dimension_point)
  (command "dimdiameter" "NEA" select_left_outer_circle left_outer_circle_dimension_point)
  (command "dimdiameter" "NEA" select_right_inner_circle right_inner_circle_dimension_point)
  (command "dimradius" "NEA" select_right_outer_circle right_outer_circle_dimension_point)
  (command "dimhorizontal" select_left_eighty_dimension_point bottom_right_vertical_axis_point eighty_horizontal_dimension_point)
  (command "dimhorizontal" eighty_horizontal_dimension_point bottom_left_vertical_axis_point two_hundred_horizontal_dimension_point)
  (command "dimvertical" select_top_vertical_dimension select_bottom_vertical_dimension vertical_dimension_point)
  (command "ZOOM" "E")
)
